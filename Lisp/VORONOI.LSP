(setq lst-a '((84.5266 96.2779)
              (84.5266 111.278)
              (84.5266 126.278)
              (84.5266 141.278)
              (84.5266 156.278)
              (84.5266 171.278)
              (84.5266 186.278)
              (84.5266 201.278)
              (84.5266 216.278)
              (84.5266 231.278)
              (84.5266 246.278)
              (84.5266 261.278)
              (84.5266 276.278)
              (84.5266 291.278)
              (84.5266 306.278)
              (109.527 96.2779)
              (109.527 111.278)
              (109.527 126.278)
              (109.527 141.278)
              (109.527 156.278)
              (109.527 171.278)
              (109.527 186.278)
              (109.527 201.278)
              (109.527 216.278)
              (109.527 231.278)
              (109.527 246.278)
              (109.527 261.278)
              (109.527 276.278)
              (109.527 291.278)
              (109.527 306.278)
              (134.527 96.2779)
              (134.527 111.278)
              (134.527 126.278)
              (134.527 141.278)
              (134.527 156.278)
              (134.527 171.278)
              (134.527 186.278)
              (134.527 201.278)
              (134.527 216.278)
              (134.527 231.278)
              (134.527 246.278)
              (134.527 261.278)
              (134.527 276.278)
              (134.527 291.278)
              (134.527 306.278)
              (159.527 96.2779)
              (159.527 111.278)
              (159.527 126.278)
              (159.527 141.278)
              (159.527 156.278)
              (159.527 171.278)
              (159.527 186.278)
              (159.527 201.278)
              (159.527 216.278)
              (159.527 231.278)
              (159.527 246.278)
              (159.527 261.278)
              (159.527 276.278)
              (159.527 291.278)
              (159.527 306.278)
              (184.527 96.2779)
              (184.527 111.278)
              (184.527 126.278)
              (184.527 141.278)
              (184.527 156.278)
              (184.527 171.278)
              (184.527 186.278)
              (184.527 201.278)
              (184.527 216.278)
              (184.527 231.278)
              (184.527 246.278)
              (184.527 261.278)
              (184.527 276.278)
              (184.527 291.278)
              (184.527 306.278)
              (209.527 96.2779)
              (209.527 111.278)
              (209.527 126.278)
              (209.527 141.278)
              (209.527 156.278)
              (209.527 171.278)
              (209.527 186.278)
              (209.527 201.278)
              (209.527 216.278)
              (209.527 231.278)
              (209.527 246.278)
              (209.527 261.278)
              (209.527 276.278)
              (209.527 291.278)
              (209.527 306.278)
              (234.527 96.2779)
              (234.527 111.278)
              (234.527 126.278)
              (234.527 141.278)
              (234.527 156.278)
              (234.527 171.278)
              (234.527 186.278)
              (234.527 201.278)
              (234.527 216.278)
              (234.527 231.278)
              (234.527 246.278)
              (234.527 261.278)
              (234.527 276.278)
              (234.527 291.278)
              (234.527 306.278)
              (259.527 96.2779)
              (259.527 111.278)
              (259.527 126.278)
              (259.527 141.278)
              (259.527 156.278)
              (259.527 171.278)
              (259.527 186.278)
              (259.527 201.278)
              (259.527 216.278)
              (259.527 231.278)
              (259.527 246.278)
              (259.527 261.278)
              (259.527 276.278)
              (259.527 291.278)
              (259.527 306.278)
              (284.527 96.2779)
              (284.527 111.278)
              (284.527 126.278)
              (284.527 141.278)
              (284.527 156.278)
              (284.527 171.278)
              (284.527 186.278)
              (284.527 201.278)
              (284.527 216.278)
              (284.527 231.278)
              (284.527 246.278)
              (284.527 261.278)
              (284.527 276.278)
              (284.527 291.278)
              (284.527 306.278)
              (309.527 96.2779)
              (309.527 111.278)
              (309.527 126.278)
              (309.527 141.278)
              (309.527 156.278)
              (309.527 171.278)
              (309.527 186.278)
              (309.527 201.278)
              (309.527 216.278)
              (309.527 231.278)
              (309.527 246.278)
              (309.527 261.278)
              (309.527 276.278)
              (309.527 291.278)
              (309.527 306.278)
              (334.527 96.2779)
              (334.527 111.278)
              (334.527 126.278)
              (334.527 141.278)
              (334.527 156.278)
              (334.527 171.278)
              (334.527 186.278)
              (334.527 201.278)
              (334.527 216.278)
              (334.527 231.278)
              (334.527 246.278)
              (334.527 261.278)
              (334.527 276.278)
              (334.527 291.278)
              (334.527 306.278)
              (359.527 96.2779)
              (359.527 111.278)
              (359.527 126.278)
              (359.527 141.278)
              (359.527 156.278)
              (359.527 171.278)
              (359.527 186.278)
              (359.527 201.278)
              (359.527 216.278)
              (359.527 231.278)
              (359.527 246.278)
              (359.527 261.278)
              (359.527 276.278)
              (359.527 291.278)
              (359.527 306.278)
              (384.527 96.2779)
              (384.527 111.278)
              (384.527 126.278)
              (384.527 141.278)
              (384.527 156.278)
              (384.527 171.278)
              (384.527 186.278)
              (384.527 201.278)
              (384.527 216.278)
              (384.527 231.278)
              (384.527 246.278)
              (384.527 261.278)
              (384.527 276.278)
              (384.527 291.278)
              (384.527 306.278)
              (409.527 96.2779)
              (409.527 111.278)
              (409.527 126.278)
              (409.527 141.278)
              (409.527 156.278)
              (409.527 171.278)
              (409.527 186.278)
              (409.527 201.278)
              (409.527 216.278)
              (409.527 231.278)
              (409.527 246.278)
              (409.527 261.278)
              (409.527 276.278)
              (409.527 291.278)
              (409.527 306.278)
              (434.527 96.2779)
              (434.527 111.278)
              (434.527 126.278)
              (434.527 141.278)
              (434.527 156.278)
              (434.527 171.278)
              (434.527 186.278)
              (434.527 201.278)
              (434.527 216.278)
              (434.527 231.278)
              (434.527 246.278)
              (434.527 261.278)
              (434.527 276.278)
              (434.527 291.278)
              (434.527 306.278)
             )
)

(defun grdrawEdge (edge / count)
    (grdraw (nth 0 edge) (nth 1 edge) 4 0)
)

(defun c:voronoiccm ()
  (foreach e (voronoiccm lst-a)
    (grdrawEdge e)
  )
)

(defun c:voronoiccm2 (/ #timer i pl ss triangle)
  (if (setq ss (ssget (list (cons 0 "POINT"))))
    (progn
      (setq #timer (getvar "date"))
      (repeat (setq i (sslength ss))
        (setq pl (cons (mapcar
                         (function +)
                         (list 0.0 0.0 0.0)
                         (cdr (assoc 10 (entget (ssname ss (setq i (1- i))))))
                       ) pl
                 )
        )
      )
      (foreach e (voronoiccm pl)
        (grdrawEdge e)
       )
      (princ(* (- (getvar "date") #timer) 86400.0))
    )
  )
  (princ)
)

(defun c:voronoicen ()
  (foreach e (voronoicen lst-a)
    (grdrawEdge e)
  )
)

(defun c:voronoicen2(/ #timer i pl ss triangle)
  (if (setq ss (ssget (list (cons 0 "POINT"))))
    (progn
      (setq #timer (getvar "date"))
      (repeat (setq i (sslength ss))
        (setq pl (cons (mapcar
                         (function +)
                         (list 0.0 0.0 0.0)
                         (cdr (assoc 10 (entget (ssname ss (setq i (1- i))))))
                       ) pl
                 )
        )
      )
      (foreach e (voronoicen pl)
        (grdrawEdge e)
       )
      (princ(* (- (getvar "date") #timer) 86400.0))
    )
  )
  (princ)
)
