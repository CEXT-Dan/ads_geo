(setq lst '((84.5266 96.2779 0.0) 
       (84.5266 111.278 0.0)
       (84.5266 126.278 0.0)
       (84.5266 141.278 0.0)
       (84.5266 156.278 0.0)
       (84.5266 171.278 0.0)
       (84.5266 186.278 0.0)
       (84.5266 201.278 0.0)
       (84.5266 216.278 0.0)
       (84.5266 231.278 0.0)
       (84.5266 246.278 0.0)
       (84.5266 261.278 0.0)
       (84.5266 276.278 0.0)
       (84.5266 291.278 0.0)
       (84.5266 306.278 0.0)
       (109.527 96.2779 0.0)
       (109.527 111.278 0.0)
       (109.527 126.278 0.0)
       (109.527 141.278 0.0)
       (109.527 156.278 0.0)
       (109.527 171.278 0.0)
       (109.527 186.278 0.0)
       (109.527 201.278 0.0)
       (109.527 216.278 0.0)
       (109.527 231.278 0.0)
       (109.527 246.278 0.0)
       (109.527 261.278 0.0)
       (109.527 276.278 0.0)
       (109.527 291.278 0.0)
       (109.527 306.278 0.0)
       (134.527 96.2779 0.0)
       (134.527 111.278 0.0)
       (134.527 126.278 0.0)
       (134.527 141.278 0.0)
       (134.527 156.278 0.0)
       (134.527 171.278 0.0)
       (134.527 186.278 0.0)
       (134.527 201.278 0.0)
       (134.527 216.278 0.0)
       (134.527 231.278 0.0)
       (134.527 246.278 0.0)
       (134.527 261.278 0.0)
       (134.527 276.278 0.0)
       (134.527 291.278 0.0)
       (134.527 306.278 0.0)
       (159.527 96.2779 0.0)
       (159.527 111.278 0.0)
       (159.527 126.278 0.0)
       (159.527 141.278 0.0)
       (159.527 156.278 0.0)
       (159.527 171.278 0.0)
       (159.527 186.278 0.0)
       (159.527 201.278 0.0)
       (159.527 216.278 0.0)
       (159.527 231.278 0.0)
       (159.527 246.278 0.0)
       (159.527 261.278 0.0)
       (159.527 276.278 0.0)
       (159.527 291.278 0.0)
       (159.527 306.278 0.0)
       (184.527 96.2779 0.0)
       (184.527 111.278 0.0)
       (184.527 126.278 0.0)
       (184.527 141.278 0.0)
       (184.527 156.278 0.0)
       (184.527 171.278 0.0)
       (184.527 186.278 0.0)
       (184.527 201.278 0.0)
       (184.527 216.278 0.0)
       (184.527 231.278 0.0)
       (184.527 246.278 0.0)
       (184.527 261.278 0.0)
       (184.527 276.278 0.0)
       (184.527 291.278 0.0)
       (184.527 306.278 0.0)
       (209.527 96.2779 0.0)
       (209.527 111.278 0.0)
       (209.527 126.278 0.0)
       (209.527 141.278 0.0)
       (209.527 156.278 0.0)
       (209.527 171.278 0.0)
       (209.527 186.278 0.0)
       (209.527 201.278 0.0)
       (209.527 216.278 0.0)
       (209.527 231.278 0.0)
       (209.527 246.278 0.0)
       (209.527 261.278 0.0)
       (209.527 276.278 0.0)
       (209.527 291.278 0.0)
       (209.527 306.278 0.0)
       (234.527 96.2779 0.0)
       (234.527 111.278 0.0)
       (234.527 126.278 0.0)
       (234.527 141.278 0.0)
       (234.527 156.278 0.0)
       (234.527 171.278 0.0)
       (234.527 186.278 0.0)
       (234.527 201.278 0.0)
       (234.527 216.278 0.0)
       (234.527 231.278 0.0)
       (234.527 246.278 0.0)
       (234.527 261.278 0.0)
       (234.527 276.278 0.0)
       (234.527 291.278 0.0)
       (234.527 306.278 0.0)
       (259.527 96.2779 0.0)
       (259.527 111.278 0.0)
       (259.527 126.278 0.0)
       (259.527 141.278 0.0)
       (259.527 156.278 0.0)
       (259.527 171.278 0.0)
       (259.527 186.278 0.0)
       (259.527 201.278 0.0)
       (259.527 216.278 0.0)
       (259.527 231.278 0.0)
       (259.527 246.278 0.0)
       (259.527 261.278 0.0)
       (259.527 276.278 0.0)
       (259.527 291.278 0.0)
       (259.527 306.278 0.0)
       (284.527 96.2779 0.0)
       (284.527 111.278 0.0)
       (284.527 126.278 0.0)
       (284.527 141.278 0.0)
       (284.527 156.278 0.0)
       (284.527 171.278 0.0)
       (284.527 186.278 0.0)
       (284.527 201.278 0.0)
       (284.527 216.278 0.0)
       (284.527 231.278 0.0)
       (284.527 246.278 0.0)
       (284.527 261.278 0.0)
       (284.527 276.278 0.0)
       (284.527 291.278 0.0)
       (284.527 306.278 0.0)
       (309.527 96.2779 0.0)
       (309.527 111.278 0.0)
       (309.527 126.278 0.0)
       (309.527 141.278 0.0)
       (309.527 156.278 0.0)
       (309.527 171.278 0.0)
       (309.527 186.278 0.0)
       (309.527 201.278 0.0)
       (309.527 216.278 0.0)
       (309.527 231.278 0.0)
       (309.527 246.278 0.0)
       (309.527 261.278 0.0)
       (309.527 276.278 0.0)
       (309.527 291.278 0.0)
       (309.527 306.278 0.0)
       (334.527 96.2779 0.0)
       (334.527 111.278 0.0)
       (334.527 126.278 0.0)
       (334.527 141.278 0.0)
       (334.527 156.278 0.0)
       (334.527 171.278 0.0)
       (334.527 186.278 0.0)
       (334.527 201.278 0.0)
       (334.527 216.278 0.0)
       (334.527 231.278 0.0)
       (334.527 246.278 0.0)
       (334.527 261.278 0.0)
       (334.527 276.278 0.0)
       (334.527 291.278 0.0)
       (334.527 306.278 0.0)
       (359.527 96.2779 0.0)
       (359.527 111.278 0.0)
       (359.527 126.278 0.0)
       (359.527 141.278 0.0)
       (359.527 156.278 0.0)
       (359.527 171.278 0.0)
       (359.527 186.278 0.0)
       (359.527 201.278 0.0)
       (359.527 216.278 0.0)
       (359.527 231.278 0.0)
       (359.527 246.278 0.0)
       (359.527 261.278 0.0)
       (359.527 276.278 0.0)
       (359.527 291.278 0.0)
       (359.527 306.278 0.0)
       (384.527 96.2779 0.0)
       (384.527 111.278 0.0)
       (384.527 126.278 0.0)
       (384.527 141.278 0.0)
       (384.527 156.278 0.0)
       (384.527 171.278 0.0)
       (384.527 186.278 0.0)
       (384.527 201.278 0.0)
       (384.527 216.278 0.0)
       (384.527 231.278 0.0)
       (384.527 246.278 0.0)
       (384.527 261.278 0.0)
       (384.527 276.278 0.0)
       (384.527 291.278 0.0)
       (384.527 306.278 0.0)
       (409.527 96.2779 0.0)
       (409.527 111.278 0.0)
       (409.527 126.278 0.0)
       (409.527 141.278 0.0)
       (409.527 156.278 0.0)
       (409.527 171.278 0.0)
       (409.527 186.278 0.0)
       (409.527 201.278 0.0)
       (409.527 216.278 0.0)
       (409.527 231.278 0.0)
       (409.527 246.278 0.0)
       (409.527 261.278 0.0)
       (409.527 276.278 0.0)
       (409.527 291.278 0.0)
       (409.527 306.278 0.0)
       (434.527 96.2779 0.0)
       (434.527 111.278 0.0)
       (434.527 126.278 0.0)
       (434.527 141.278 0.0)
       (434.527 156.278 0.0)
       (434.527 171.278 0.0)
       (434.527 186.278 0.0)
       (434.527 201.278 0.0)
       (434.527 216.278 0.0)
       (434.527 231.278 0.0)
       (434.527 246.278 0.0)
       (434.527 261.278 0.0)
       (434.527 276.278 0.0)
       (434.527 291.278 0.0)
       (434.527 306.278 0.0)
      )
)
(defun C:TEST1 ()
  (kdtreecreate lst)
  (setq kdr (kdtreeradiusSearch '(284 156 0.0) 1500))
  (kdtreedestroy)
  kdr
)
(defun C:TEST2 ()
  (kdtreecreate lst)
  (setq kdr (kdtreeknnSearch '(284 156 0.0) 1))
  (kdtreedestroy)
  kdr
)
(defun C:TEST3 ()
  (kdtreecreate lst)
  (setq kdr (kdtreepoints))
  (kdtreedestroy)
  kdr
)

(defun C:TEST4 ()
  (setq count 0)
	(while (< count 10)
		(mapinsert count (nth count lst))
		(setq count (1+ count))
	)
)

(defun C:TEST5 ()
  (setq count 0)
	(while (< count 10)
		(setinsert (nth count lst))
		(setq count (1+ count))
	)
)

(setq lst2 '((84.5266 96.2779 0.0) 
       (84.5266 111.278 0.0)
       (84.5266 126.278 0.0)
       ))
       
; list of points
(defun C:TEST6 ()
  (mapclear)
  (setq count 0)
	(foreach n lst2
		(mapinsert n count)
		(setq count (1+ count))
	)
	(mapgetat (nth 1 lst2))
	;(mapgetall)
)

;(((84.5266 111.278 0.0) 1) ((84.5266 96.2779 0.0) 0) ((84.5266 126.278 0.0) 2))
